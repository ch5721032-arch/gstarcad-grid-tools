;; polar-tracking.lsp - Polar tracking angle presets
;; Commands: TRACK45 / TRACK15 / TRACKOFF
(defun c:TRACK45 ( )
  (setvar "POLARANG" (/ pi 4.0))
  (setvar "POLARMODE" 1)
  (princ "\nPolar angle set to 45 degrees.")
  (princ)
)
(defun c:TRACK15 ( )
  (setvar "POLARANG" (/ pi 12.0))
  (setvar "POLARMODE" 1)
  (princ "\nPolar angle set to 15 degrees.")
  (princ)
)
(defun c:TRACKOFF ( )
  (setvar "POLARMODE" 0)
  (princ "\nPolar tracking off.")
  (princ)
)
